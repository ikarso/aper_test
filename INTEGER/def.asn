Example1 DEFINITIONS ::=
BEGIN

Message ::= SEQUENCE {
	id7bit	INTEGER (0..127),
	id8bit	INTEGER (0..255),
	id16bit	INTEGER (0..65535),
	id24bit INTEGER (0..16777215),
	id32bit	INTEGER (0..4294967295),
	id48bit INTEGER (0..281474976710655),
	id51bit INTEGER (0..2251799813685247),
	enable	BOOLEAN
}

END
