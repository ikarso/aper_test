Example1 DEFINITIONS ::=
BEGIN

Message ::= SEQUENCE {
	id7bit	INTEGER (-64..63),
	id8bit	INTEGER (-128..127),
	id16bit	INTEGER (-32768..32767),
	id24bit INTEGER (-8388608..8388607),
	id32bit	INTEGER (-2147483648..2147483647),
	id48bit INTEGER (0..281474976710655),
	id51bit INTEGER (0..2251799813685247),
	enable	BOOLEAN
}

END
